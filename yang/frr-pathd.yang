module frr-pathd {
  yang-version 1.1;
  namespace "http://frrouting.org/yang/pathd";
  prefix frr-pathd;

  import ietf-inet-types {
    prefix inet;
  }
  import ietf-yang-types {
    prefix yang;
  }
  import ietf-routing-types {
    prefix rt-types;
  }
  import frr-interface {
    prefix frr-interface;
  }

  organization
    "Free Range Routing";
  contact
    "FRR Users List:       <mailto:frog@lists.frrouting.org>
     FRR Development List: <mailto:dev@lists.frrouting.org>";
  description
    "This module defines a model for managing FRR pathd daemon.";

  revision 2018-11-06 {
    description
      "Initial revision.";
  }

  typedef protocol-origin-type {
    description
      "Indication for the protocol origin of an object.";
    type enumeration {
      enum pcep {
        value 1;
        description "The object was created through PCEP";
      }
      enum bgp {
        value 2;
        description "The object was created through GBP";
      }
      enum local {
        value 3;
        description "The object was created through CLI, Yang model via Netconf, gRPC, etc";
      }
    }
  }

  typedef originator-type {
        type string {
          length "1..64";
        }
        description
          "Identifier of the originator of an object, could be 'config', '1.1.1.1:4189' or '2001:db8:85a3::8a2e:370:7334:4189'";
      }

  container pathd {
    list segment-list {
      key "name";
      description "Segment-list properties";
      leaf name {
        type string {
          length "1..64";
        }
        description "Segment-list name";
      }
      leaf protocol-origin {
        type protocol-origin-type;
        mandatory true;
        description
          "Indication for the protocol origin of the segment list.";
      }
      leaf originator {
        type originator-type;
        mandatory true;
        description "Originator of the segment list";
      }
      list segment {
        key "index";
        description "Configure Segment/hop at the index";
        leaf index {
          type uint32;
          description "Segment index";
        }
        leaf sid-value {
          type rt-types:mpls-label;
          mandatory true;
          description "MPLS label value";
        }
        container nai {
          presence "The segement has a Node or Adjacency Identifier";
          leaf type {
            description "NAI type";
            mandatory true;
            type enumeration {
              enum ipv4_node {
                value 1;
                description "IPv4 node identifier";
              }
              enum ipv6_node {
                value 2;
                description "IPv6 node identifier";
              }
              enum ipv4_adjacency {
                value 3;
                description "IPv4 adjacency";
              }
              enum ipv6_adjacency {
                value 4;
                description "IPv6 adjacency";
              }
              enum ipv4_unnumbered_adjacency {
                value 5;
                description "IPv4 unnumbered adjacency";
              }
            }
          }
          leaf local-address {
            type inet:ip-address;
            mandatory true;
          }
          leaf local-interface {
            type uint32;
            mandatory true;
            when "../type = 'ipv4_unnumbered_adjacency'";
          }
          leaf remote-address {
            type inet:ip-address;
            mandatory true;
            when "../type = 'ipv4_adjacency' or ../type = 'ipv6_adjacency' or ../type = 'ipv4_unnumbered_adjacency'";
          }
          leaf remote-interface {
            type uint32;
            mandatory true;
            when "../type = 'ipv4_unnumbered_adjacency'";
          }
        }
      }
    }
    list sr-policy {
      key "color endpoint";
      unique "name";
      leaf color {
        type uint32;
        description
          "Color of the SR Policy.";
      }
      leaf endpoint {
        type inet:ip-address;
        description
          "Indication for the endpoint of the SR Policy.";
      }
      leaf name {
        type string {
          length "1..64";
        }
        description
          "Name of the SR Policy.";
      }
      leaf binding-sid {
        type rt-types:mpls-label;
        description
          "BSID of the SR Policy.";
      }
      leaf is-operational {
        type boolean;
        config false;
        description
          "True if a valid candidate path of this policy is operational in zebra, False otherwise";
      }
      list candidate-path {
        unique "name";
        description
          "List of Candidate Paths of the SR Policy.";
        key "preference";
        leaf preference {
          type uint32;
          description
            "Administrative preference.";
        }
        leaf name {
          type string {
            length "1..64";
          }
          mandatory true;
          description
            "Symbolic Name of the Candidate Path.";
        }
        leaf is-best-candidate-path {
          type boolean;
          config false;
          description
            "True if the candidate path is the best candidate path, False otherwise";
        }
        leaf protocol-origin {
          type protocol-origin-type;
          mandatory true;
          description
            "Indication for the protocol origin of the Candidate Path.";
        }
        leaf originator {
          type originator-type;
          mandatory true;
          description "Originator of the candidate path";
        }
        leaf discriminator {
          type uint32;
          config false;
          description "Candidate path distinguisher";
        }
        leaf type {
          description
            "Type of the Candidate Path.";
          mandatory true;
          type enumeration {
            enum explicit {
              value 1;
            }
            enum dynamic {
              value 2;
            }
          }
        }
        leaf segment-list-name {
          type leafref {
            path ../../../segment-list/name;
          }
          description
            "The name of the Segment List to use as LSP.";
        }
        leaf bandwidth {
          type decimal64 {
            fraction-digits 6;
          }
          description
            "The bandwidth required by the candidate path.";
        }
        list metrics {
          key "type";
          leaf type {
            description
              "Type of the metric.";
            type enumeration {
              enum abc {
                value 1;
                description "Agreggate Bandwidth Consumption Metric";
              }
              enum te {
                value 2;
                description "Traffic Engeneering Metric";
              }
            }
          }
          leaf is-bound {
            type boolean;
            description
              "Defines if the value is a bound (a maximum) for the path metric that must not be exceeded.";
          }
          leaf is-computed {
            type boolean;
            description
              "Defines if the value has been generated by the originator of the path.";
          }
          leaf value {
            mandatory true;
            type decimal64 {
                fraction-digits 6;
            }
          }
        }
      }
    }
  }
}
